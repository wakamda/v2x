/**
 * 定义车辆尺寸大小。由车辆长宽高三个维度来定义尺寸，其中高度数值为可选项。
 */
VehSize DEFINITIONS AUTOMATIC TAGS ::= BEGIN

-- imports and exports

EXPORTS VehicleSize;
IMPORTS ;
	
	VehicleSize ::= SEQUENCE {
		width VehicleWidth,
		length VehicleLength,
		height VehicleHeight OPTIONAL
	}
	
	VehicleWidth ::= INTEGER (0..1023) 
	-- LSB units are 1 cm with a range of >10 meters
	
	VehicleLength ::= INTEGER (0.. 4095)
	-- LSB units of 1 cm with a range of >40 meters
	
	VehicleHeight ::= INTEGER (0..127)
	-- LSB units of 5 cm, range to 6.35 meters
	
END
