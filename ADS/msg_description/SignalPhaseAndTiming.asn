/**
 * SPAT信号灯信息
 */
SignalPhaseAndTiming DEFINITIONS AUTOMATIC TAGS ::= BEGIN

-- imports and exports

EXPORTS SPAT;
IMPORTS MinuteOfTheYear FROM DefTime
		DescriptiveName FROM MapNode
		IntersectionStateList FROM SPATIntersectionState
		MsgCount FROM MsgFrame;
	
	SPAT ::= SEQUENCE {
		msgCnt MsgCount,						-- 消息编号，用于收包的监控和丢包的统计
		timeStamp MinuteOfTheYear OPTIONAL,		-- 当前年份，已经过去的总分钟数（UTC时间）。
		name DescriptiveName OPTIONAL,			-- RSU名称
		-- human readable name for this collection
		-- to be used only in debug mode
		intersections IntersectionStateList,	-- 信号灯状态
		-- sets of SPAT data (one per intersection)
		...
	}
	
END
