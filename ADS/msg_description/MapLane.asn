/**
 * 车道信息
 */
MapLane DEFINITIONS AUTOMATIC TAGS ::= BEGIN

-- imports and exports

EXPORTS LaneList, LaneWidth;
IMPORTS PointList FROM MapPoint
		NodeReferenceID FROM MapNode
		SpeedLimitList FROM MapSpeedLimit
		PhaseID FROM SPATIntersectionState;
	
	LaneList ::= SEQUENCE (SIZE(1..32)) OF Lane
	
	-- 车道
	-- 包含ID、共享属性、车道出口的允许转向行为、车道与下游路段车道的连接关系列表以及车道中间点列表。
	Lane ::= SEQUENCE {
		laneID LaneID,								-- 车道id

		laneAttributes LaneAttributes OPTIONAL,		-- 车道共享属性和其他属性
		-- Define basic attribute of lane
		maneuvers AllowedManeuvers OPTIONAL,		-- 车道转向属性
		-- the permitted maneuvers for this lane
		connectsTo ConnectsToList OPTIONAL,			-- 下游车道的连接列表及属性
		-- connection to downsteam lanes
		speedLimits SpeedLimitList OPTIONAL,		--车道限速列表
		-- List all the speed limits
		points PointList OPTIONAL,					-- 节点列表
		-- Define road points and segments
		...
	}
	
	-- 车道id
	-- 车道定义在每一条有向路段上，同一条有向路段上的每个车道，都拥有一个单独的ID。车道号，以该车道行驶方向为参考，自左向右从1开始编号。
	-- ID为0表示无效ID。
	-- the value 255 is reserved for future use
	LaneID ::= INTEGER (0..255) 
	
	
	-- 定义车道宽度
	-- 分辨率为1 cm
	LaneWidth ::= INTEGER (0..32767) 
	
	-- 定义路段中每条车道，在下游路口处与下游路段中车道的转向连接关系列表。
	ConnectsToList ::= SEQUENCE (SIZE(1..8)) OF Connection
	
	-- 定义当前车道与下游路段中车道的连接关系。
	-- 包括下游路段出口节点ID、连接的下游路段车道基本信息以及对应的信号灯相位号。在车道连接中
	-- 定义的相位号，是对DF_Movement中定义转向的相位号的一个补充。当某一些车道在转向时需要参考一
	-- 些特殊的信号灯相位（而不是DF_Movement中定义的默认相位），则应该将其定义在本数据帧中。
	Connection::= SEQUENCE {
		remoteIntersection NodeReferenceID,			--下游节点id

		connectingLane ConnectingLane OPTIONAL,		-- 下游车道及转向允许
		-- The index of the connecting lane and also
		-- the maneuver from the current lane to it
		-- When we want to list the allowed lanes of the next link
		-- this lane can lead to, we use this entry
		phaseId PhaseID OPTIONAL
		-- The matching signal group send by
		-- the SPAT message for this lane/maneuver.
		-- Shall be present unless the connectingLane
		-- has no signal group (is un-signalized)
	}
	
	-- 用于定位上游车道转向连接的下游车道。
	-- 包括下游车道ID以及该转向的允许行驶行为，下游车道ID的作用范围是该车道所在的路段。
	ConnectingLane ::= SEQUENCE {
		lane LaneID, 						-- 下游车道id
		maneuver AllowedManeuvers OPTIONAL	-- 下游车道转向行为
		-- The Maneuver between
		-- the enclosing lane and this lane
		-- at the stop line to connect them
		}
	
	-- 定义一个（机动车）车道的允许转向行为。
	AllowedManeuvers ::= BIT STRING {
		-- With bits as defined:
		-- Allowed maneuvers at path end (stop line)
		-- All maneuvers with bits not set are therefore prohibited
		-- A value of zero shall be used for unknown, indicating no Maneuver
		maneuverStraightAllowed (0),
		-- a Straight movement is allowed in this lane
		maneuverLeftAllowed (1),
		-- a Left Turn movement is allowed in this lane
		maneuverRightAllowed (2),
		-- a Right Turn movement is allowed in this lane
		maneuverUTurnAllowed (3),
		-- a U turn movement is allowed in this lane
		maneuverLeftTurnOnRedAllowed (4),
		-- a Stop, and then proceed when safe movement
		-- is allowed in this lane
		maneuverRightTurnOnRedAllowed (5),
		-- a Stop, and then proceed when safe movement
		-- is allowed in this lane
		maneuverLaneChangeAllowed (6),
		-- a movement which changes to an outer lane
		-- on the egress side is allowed in this lane
		-- (example: left into either outbound lane)
		maneuverNoStoppingAllowed (7),
		-- the vehicle should not stop at the stop line
		-- (example: a flashing green arrow)
		yieldAllwaysRequired (8),
		-- the allowed movements above are not protected
		-- (example: an permanent yellow condition)
		goWithHalt (9),
		-- after making a full stop, may proceed
		caution (10),
		-- proceed past stop line with caution
		reserved1 (11)
		-- used to align to 12 Bit Field
		} (SIZE(12))
	
	-- 车道属性集合
	LaneAttributes ::= SEQUENCE {
		shareWith LaneSharing OPTIONAL,		-- 共享属性
		laneType LaneTypeAttributes			-- 分类各种车道的属性
	}
	
	-- 定义车道被共享的情况。在已有的车道属性定义基础上，该数据表示此车道还会有其他的交通参与者者出现，并可能拥有相同的路权。
	-- 数据中每一位置“1”表示对应的车道共享属性生效。
	LaneSharing ::= BIT STRING {
		overlappingLaneDescriptionProvided (0),
		multipleLanesTreatedAsOneLane (1),
		otherNonMotorizedTrafficTypes (2),
		individualMotorizedVehicleTraffic (3),
		busVehicleTraffic (4),
		taxiVehicleTraffic (5),
		pedestriansTraffic (6),
		cyclistVehicleTraffic (7),
		trackedVehicleTraffic (8),
		pedestrianTraffic (9)
		} (SIZE (10))
		
	-- 定义不同类别车道的属性集合
	LaneTypeAttributes ::= CHOICE {
		vehicle LaneAttributes-Vehicle, 				-- 行车道
		crosswalk LaneAttributes-Crosswalk, 			-- 人行横道
		bikeLane LaneAttributes-Bike, 					-- 自行车道
		sidewalk LaneAttributes-Sidewalk, 				-- 人行道
		median LaneAttributes-Barrier, 					-- 车道隔离
		striping LaneAttributes-Striping, 				-- 标线车道
		trackedVehicle LaneAttributes-TrackedVehicle, 	-- 轨道
		parking LaneAttributes-Parking, 				-- 停车道
		...
		}
		
	-- 车辆行驶车道的属性定义。用来描述一条车用车道的特殊属性和其允许行驶的汽车种类。
	LaneAttributes-Vehicle ::= BIT STRING { 
		isVehicleRevocableLane (0),
		-- this lane may be activated or not based
		-- on the current SPAT message contents
		-- if not asserted, the lane is ALWAYS present
		isVehicleFlyOverLane (1),
		-- path of lane is not at grade
		hovLaneUseOnly (2),
		restrictedToBusUse (3),
		restrictedToTaxiUse (4),
		restrictedFromPublicUse (5),
		hasIRbeaconCoverage (6),
		permissionOnRequest (7) -- e.g. to inform about a lane for e-cars
		} (SIZE (8,...))
		
	-- 人行横道的属性定义。指示车道的一系列通过属性和人行辅助设施。
	LaneAttributes-Crosswalk ::= BIT STRING { 
		-- With bits as defined: 
		-- MUTCD provides no suitable "types" to use here
		crosswalkRevocableLane (0),
		-- this lane may be activated or not based
		-- on the current SPAT message contents
		-- if not asserted, the lane is ALWAYS present
		bicyleUseAllowed (1),
		-- The path allows bicycle traffic,
		-- if not set, this mode is prohibited
		isXwalkFlyOverLane (2),
		-- path of lane is not at grade
		fixedCycleTime (3),
		-- ped walk phases use preset times
		-- i.e. there is not a 'push to cross' button
		biDirectionalCycleTimes (4),
		-- ped walk phases use different SignalGroupID
		-- for each direction. The first SignalGroupID
		-- in the first Connection represents 'inbound'
		-- flow (the direction of travel towards the first
		-- node point) while second SignalGroupID in the
		-- next Connection entry represents the 'outbound'
		-- flow. And use of RestrictionClassID entries
		-- in the Connect follow this same pattern in pairs.
		hasPushToWalkButton (5),
		-- Has a demand input
		audioSupport (6),
		-- audio crossing cues present
		rfSignalRequestPresent (7),
		-- Supports RF push to walk technologies
		unsignalizedSegmentsPresent (8)
		-- The lane path consists of one of more segments
		-- which are not part of a signal group ID
		-- Bits 9~15 reserved and set to zero
	} (SIZE (16))
	
	-- 自行车道属性
	LaneAttributes-Bike ::= BIT STRING { 
		-- With bits as defined:
		bikeRevocableLane (0),
		-- this lane may be activated or not based
		-- on the current SPAT message contents
		-- if not asserted, the lane is ALWAYS present
		pedestrianUseAllowed (1),
		-- The path allows pedestrian traffic,
		-- if not set, this mode is prohibited
		isBikeFlyOverLane (2),
		-- path of lane is not at grade
		fixedCycleTime (3),
		-- the phases use preset times
		-- i.e. there is not a 'push to cross' button
		biDirectionalCycleTimes (4),
		-- ped walk phases use different SignalGroupID
		-- for each direction. The first SignalGroupID
		-- in the first Connection represents 'inbound'
		-- flow (the direction of travel towards the first
		-- node point) while second SignalGroupID in the
		-- next Connection entry represents the 'outbound'
		-- flow. And use of RestrictionClassID entries
		-- in the Connect follow this same pattern in pairs.
		isolatedByBarrier (5),
		unsignalizedSegmentsPresent (6)
		-- The lane path consists of one of more segments
		-- which are not part of a signal group ID
		-- Bits 7~15 reserved and set to zero
		} (SIZE (16))
		
	-- 人行道的属性定义。
	LaneAttributes-Sidewalk ::= BIT STRING { 
		-- With bits as defined:
		sidewalk-RevocableLane (0),
		-- this lane may be activated or not based
		-- on the current SPAT message contents
		-- if not asserted, the lane is ALWAYS present
		bicyleUseAllowed (1),
		-- The path allows bicycle traffic,
		-- if not set, this mode is prohibited
		isSidewalkFlyOverLane (2),
		-- path of lane is not at grade
		walkBikes (3)
		-- bike traffic must dismount and walk 
		-- Bits 4~15 reserved and set to zero
		} (SIZE (16))
		
	-- 车道隔离的属性定义。主要指示车道隔离的物理形式。
	LaneAttributes-Barrier ::= BIT STRING { 
		-- With bits as defined:
		median-RevocableLane (0),
		-- this lane may be activated or not based
		-- on the current SPAT message contents
		-- if not asserted, the lane is ALWAYS present
		median (1),
		whiteLineHashing (2),
		stripedLines (3),
		doubleStripedLines (4),
		trafficCones (5),
		constructionBarrier (6),
		trafficChannels (7),
		lowCurbs (8),
		highCurbs (9) -- Bits 10~15 reserved and set to zero
		} (SIZE (16))
		
	-- 标线车道的属性定义。指示了车道上网纹或者标志标线所传达的道路信息，如禁行、路线标识等，
	-- 辅助驾驶员通过一些复杂的路口或路段，提高驾驶安全性。
	LaneAttributes-Striping ::= BIT STRING { 
		-- With bits as defined:
		stripeToConnectingLanesRevocableLane (0),
		-- this lane may be activated or not activated based
		-- on the current SPAT message contents
		-- if not asserted, the lane is ALWAYS present
		stripeDrawOnLeft (1),
		stripeDrawOnRight (2),
		-- which side of lane to mark
		stripeToConnectingLanesLeft (3),
		stripeToConnectingLanesRight (4),
		stripeToConnectingLanesAhead (5)
		-- the stripe type should be
		-- presented to the user visually
		-- to reflect stripes in the
		-- intersection for the type of
		-- movement indicated 
		-- Bits 6~15 reserved and set to zero
		} (SIZE (16))
		
	-- 轨道车辆车道的属性定义。用来描述一条轨道车辆车道的特殊属性和其允许行驶的车辆种类
	LaneAttributes-TrackedVehicle ::= BIT STRING { 
		-- With bits as defined:
		spec-RevocableLane (0),
		-- this lane may be activated or not based
		-- on the current SPAT message contents
		-- if not asserted, the lane is ALWAYS present
		spec-commuterRailRoadTrack (1),
		spec-lightRailRoadTrack (2),
		spec-heavyRailRoadTrack (3),
		spec-otherRailType (4) -- Bits 5~15 reserved and set to zero
		} (SIZE (16))
		
	-- 停车车道的属性定义。指示车道允许停车的种类和停靠方式。
	LaneAttributes-Parking ::= BIT STRING {
		-- With bits as defined:
		-- Parking use details, note that detailed restrictions such as
		-- allowed hours are sent by way of ITIS codes in the TIM message
		parkingRevocableLane (0),
		-- this lane may be activated or not based
		-- on the current SPAT message contents
		-- if not asserted, the lane is ALWAYS present
		parallelParkingInUse (1),
		headInParkingInUse (2),
		doNotParkZone (3),
		-- used to denote fire hydrants as well as
		-- short disruptions in a parking zone
		parkingForBusUse (4),
		parkingForTaxiUse (5),
		noPublicParkingUse (6)
		-- private parking, as in front of
		-- private property 
		-- Bits 7~15 reserved and set to zero
		} (SIZE (16))
	
END
