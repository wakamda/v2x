/**
 * 定义经纬度和高度的偏差值
 * 经纬度和高度的偏差值的数据表示和真实数据表示方法不同，都分别由7种比特位组表示，分辨率都相同，所以能表示的范围不同 
 * 三维偏差值和node中的refPos值（参考值）对应，三维偏移量也就是偏差值，都是由真实值减去参考值计算出来的
 */
DefPositionOffset DEFINITIONS AUTOMATIC TAGS ::= BEGIN

-- imports and exports

EXPORTS PositionOffsetLLV;
IMPORTS Longitude, Latitude, Elevation FROM DefPosition;
	
	-- 定义三维的偏差值（相对位置）（相对经纬度和相对高程）。约定偏差值等于真实值减去参考值。
	PositionOffsetLLV ::= SEQUENCE {
		offsetLL PositionOffsetLL,		-- 经纬度偏差
		offsetV VerticalOffset OPTIONAL -- 高度偏差
	}
	
	-- 12比特数值，表示当前位置点关于参考位置点的经纬度偏差。
	-- 值得注意的是，根据纬度的不同，相同的经纬度偏差值对应的实际球面距离可能不同。
	-- 关于参考点，向东或向北偏移，数值为正，反之为负。分辨率为1e-7°。
	-- A range of +- 0.0002047 degrees 
	-- In LSB units of 0.1 microdegrees 
	OffsetLL-B12 ::= INTEGER (-2048..2047) 

	-- 14比特数值
	-- A range of +- 0.0008191 degrees 
	-- In LSB units of 0.1 microdegrees
	OffsetLL-B14 ::= INTEGER (-8192..8191) 

	-- 16比特数值
	-- A range of +- 0.0032767 degrees 
	-- In LSB units of 0.1 microdegrees
	OffsetLL-B16 ::= INTEGER (-32768..32767) 

	OffsetLL-B18 ::= INTEGER (-131072..131071) 
	-- A range of +- 0.0131071 degrees 
	-- In LSB units of 0.1 microdegrees
	OffsetLL-B22 ::= INTEGER (-2097152..2097151) 
	-- A range of +- 0.2097151 degrees 
	-- In LSB units of 0.1 microdegrees
	OffsetLL-B24 ::= INTEGER (-8388608..8388607) 
	-- A range of +- 0.8388607 degrees 
	-- In LSB units of 0.1 microdegrees
	
	-- 24比特相对经纬度位置，表示当前位置点关于参考位置点的经纬度偏差。由两个12比特的经度、纬度偏差值组成。
	-- ranges of +- 0.0002047 degrees 
	-- ranges of +- 22.634554 meters at the equator
	Position-LL-24B ::= SEQUENCE { 
		lon OffsetLL-B12,
		lat OffsetLL-B12
		}
	-- 28比特相对经纬度位置，表示当前位置点关于参考位置点的经纬度偏差。由两个14比特的经度、纬度偏差值组成。
	-- ranges of +- 0.0008191 degrees 
	-- ranges of +- 90.571389 meters at the equator
	Position-LL-28B ::= SEQUENCE { 
		lon OffsetLL-B14,
		lat OffsetLL-B14
		}
	
	-- 32比特相对经纬度位置，表示当前位置点关于参考位置点的经纬度偏差。由两个16比特的经度、纬度偏差值组成。
	-- ranges of +- 0.0032767 degrees 
	-- ranges of +- 362.31873 meters at the equator
	Position-LL-32B ::= SEQUENCE { 
		lon OffsetLL-B16,
		lat OffsetLL-B16
		}
	
	-- 36比特相对经纬度位置
	-- ranges of +- 0.0131071 degrees 
	-- ranges of +- 01.449308 Kmeters at the equator
	Position-LL-36B ::= SEQUENCE { 
		lon OffsetLL-B18,
		lat OffsetLL-B18
		}

	-- 44比特相对经纬度位置
	-- ranges of +- 0.2097151 degrees 
	-- ranges of +- 23.189096 Kmeters at the equator
	Position-LL-44B ::= SEQUENCE { 
		lon OffsetLL-B22,
		lat OffsetLL-B22
		}
	
	-- 48比特相对经纬度位置
	-- ranges of +- 0.8388607 degrees 
	-- ranges of +- 92.756481 Kmeters at the equator
	Position-LL-48B ::= SEQUENCE { 
		lon OffsetLL-B24,
		lat OffsetLL-B24
		}
	
	-- 64比特经纬度位置。实际上，该尺度采用了真实经纬度数据进行描述，非相对位置。
	Position-LLmD-64b ::= SEQUENCE {
		lon Longitude,
		lat Latitude
		}
	
	-- 经纬度偏差，来描述一个坐标点的相对位置。约定偏差值等于真实值减去参考值。提供了7 种尺度的描述方式。
	PositionOffsetLL ::= CHOICE { 
		-- Locations with LL content Span at the equator when using a zoom of one:
		position-LL1 Position-LL-24B, 
		-- within +- 22.634554 meters of the reference position
		position-LL2 Position-LL-28B, 
		-- within +- 90.571389 meters of the reference position
		position-LL3 Position-LL-32B, 
		-- within +- 362.31873 meters of the reference position
		position-LL4 Position-LL-36B, 
		-- within +- 01.449308 Kmeters of the reference position
		position-LL5 Position-LL-44B, 
		-- within +- 23.189096 Kmeters of the reference position
		position-LL6 Position-LL-48B, 
		-- within +- 92.756481 Kmeters of the reference position
		position-LatLon Position-LLmD-64b 
		-- node is a full 32b Lat/Lon range
	}
	
	-- 定义垂直方向位置偏差。提供了7种尺度范围的偏差表示方式。
	VerticalOffset ::= CHOICE { 
		offset1 VertOffset-B07, -- with a range of +- 6.3 meters vertical
		offset2 VertOffset-B08, -- with a range of +- 12.7 meters vertical
		offset3 VertOffset-B09, -- with a range of +- 25.5 meters vertical
		offset4 VertOffset-B10, -- with a range of +- 51.1 meters vertical
		offset5 VertOffset-B11, -- with a range of +- 102.3 meters vertical
		offset6 VertOffset-B12, -- with a range of +- 204.7 meters vertical
		elevation Elevation -- with a range of -409.5 to + 6143.9 meters
		}
	
	-- 7比特的数据，定义垂直方向（Z轴）关于参考位置点的偏差。顺着Z轴方向为正。数据分辨率为10 cm。
	-- -64数值表示未知大小。
	VertOffset-B07 ::= INTEGER (-64..63) 
	-- LSB units of of 10 cm 
	-- with a range of +- 6.3 meters vertical 
	-- value 63 to be used for 63 or greater 
	-- value -63 to be used for -63 or greater 
	-- value -64 to be unavailable
	
	VertOffset-B08 ::= INTEGER (-128..127) 
	-- LSB units of of 10 cm 
	-- with a range of +- 12.7 meters vertical 
	-- value 127 to be used for 127 or greater 
	-- value -127 to be used for -127 or greater 
	-- value -128 to be unavailable
	
	VertOffset-B09 ::= INTEGER (-256..255) 
	-- LSB units of of 10 cm 
	-- with a range of +- 25.5 meters vertical 
	-- value 255 to be used for 255 or greater 
	-- value -255 to be used for -255 or greater 
	-- value -256 to be unavailable
	
	VertOffset-B10 ::= INTEGER (-512..511) 
	-- LSB units of of 10 cm 
	-- with a range of +- 51.1 meters vertical 
	-- value 511 to be used for 511 or greater 
	-- value -511 to be used for -511 or greater 
	-- value -512 to be unavailable
	
	VertOffset-B11 ::= INTEGER (-1024..1023) 
	-- LSB units of of 10 cm 
	-- with a range of +- 102.3 meters vertical 
	-- value 1023 to be used for 1023 or greater 
	-- value -1023 to be used for -1023 or greater 
	-- value -1024 to be unavailable
	
	VertOffset-B12 ::= INTEGER (-2048..2047) 
	-- LSB units of of 10 cm 
	-- with a range of +- 204.7 meters vertical 
	-- value 2047 to be used for 2047 or greater 
	-- value -2047 to be used for -2047 or greater 
	-- value -2048 to be unavailable
	
END
