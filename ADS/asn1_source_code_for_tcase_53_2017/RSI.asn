/**
 * 交通事件信息以及交通标志信息。
 */
RSI DEFINITIONS AUTOMATIC TAGS ::= BEGIN

-- imports and exports

EXPORTS RoadSideInformation;
IMPORTS MsgCount FROM MsgFrame
		MinuteOfTheYear FROM DefTime
		Position3D FROM DefPosition;
	
	RoadSideInformation ::= SEQUENCE {
		msgCnt MsgCount,									-- 消息编号，用于收包的监控和丢包的统计
		timeStamp MinuteOfTheYear OPTIONAL,					-- 当前年份，已经过去的总分钟数（UTC时间）。
		id OCTET STRING (SIZE(8)),							-- 发送消息的RSU id
		rsiId INTEGER (0..255),								-- local ID of this rsi information set by RSU
		refPos Position3D, 									-- 交通标志或事故（也就是发送该消息的RSU）的三维的坐标位置，经纬度和高程。
		rtes RTEList OPTIONAL,								-- 交通标志或事故的内容
		-- All the rte data packed in this message
		rtss RTSList OPTIONAL,							
		-- All the rts data packed in this message
		...
	}

END
