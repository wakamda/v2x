/**
 * 
 */
RSM DEFINITIONS AUTOMATIC TAGS ::= BEGIN

-- imports and exports

EXPORTS RoadsideSafetyMessage;
IMPORTS AccelerationSet4Way FROM DefAcceleration
		VehicleSize FROM VehSize
		Position3D, PositionConfidenceSet FROM DefPosition
		DSecond FROM DefTime
		Speed, Heading, SteeringWheelAngle, MotionConfidenceSet FROM DefMotion
		TransmissionState FROM VehStatus
		MsgCount FROM MsgFrame
		VehicleClassification FROM VehClass
		PositionOffsetLLV FROM DefPositionOffset;
	
	RoadsideSafetyMessage ::= SEQUENCE {
		msgCnt MsgCount,				-- 消息编号，用于收包的监控和丢包的统计
		id OCTET STRING (SIZE(8)),		-- RSU ID
		refPos Position3D,				-- RSU 三维的坐标位置，经纬度和高程。
		participants ParticipantList,	-- 交通参与者列表
		-- All or part of the participants 
		-- detected by RSU
		...
	}
	
	-- 定义交通参与者列表。应用于RSM消息中，表示RSU当前探测到的所有或者部分交通参与者信息。
	ParticipantList ::= SEQUENCE (SIZE(1..16)) OF ParticipantData
	
	-- 定义交通参与者的基本安全信息，包括RSU自身以及RSU依靠感知手段获取的机动车、非机动车等交通参与者。
	-- 该参与者数据帧相当于OBU车辆自身广播的BSM消息，它由RSU感知并发送给周边网联车辆。
	-- 当该参与者信息来源于RSU收到的BSM消息时，其中的id字段必须与BSM中的车辆id字段一致。
	ParticipantData ::= SEQUENCE {
		ptcType ParticipantType,						-- 交通参与者类型
		ptcId INTEGER (0..65535),						-- RSU设置的临时ID
		-- 0 is RSU itself
		-- 1 . .255表示RSU检测到的参与者
		source SourceType,								-- 数据的来源
		id OCTET STRING (SIZE(8)) OPTIONAL,				-- 数据源id
		plateNo OCTET STRING (SIZE(4..16)) OPTIONAL,	
		secMark DSecond,								-- 定义1分钟内的毫秒级时刻。
		pos PositionOffsetLLV,							-- 三维的偏差值
		accuracy PositionConfidenceSet,					-- 当前实时位置（经纬度和高程）的精度大小
		transmission TransmissionState OPTIONAL,		-- 车辆档位状态 
		speed Speed,									-- 车速
		heading Heading,								-- 航向角
		angle SteeringWheelAngle OPTIONAL,				-- 方向盘转角
		motionCfd MotionConfidenceSet OPTIONAL,			-- 车速精度、航向精度和方向盘转角的精度
		accelSet AccelerationSet4Way OPTIONAL,			-- 车辆四轴加速度
		size VehicleSize,								-- 车辆尺寸
		vehicleClass VehicleClassification OPTIONAL,	-- 车辆的种类
		...
	}

	-- 路侧单元检测到的交通参与者类型。
	ParticipantType ::= ENUMERATED {
		unknown (0), -- B'0000 Unknown
		motor (1), -- B'0001 motor
		non-motor (2), -- B'0010 non-motor
		pedestrian (3), -- B'0011 pedestrian
		rsu (4), -- B'0100 rsu
		...
		}
	
	-- 定义交通参与者数据的来源。包括以下类型：
	-- ——unknown：未知数据源类型；
	-- ——selfinfo：RSU 自身信息；
	-- ——v2x：来源于参与者自身的v2x 广播消息；
	-- ——video：来源于视频传感器；
	-- ——microwaveRadar：来源于微波雷达传感器；
	-- ——loop：来源于地磁线圈传感器；
	-- ——lidar：来源于激光雷达传感器；
	-- ——integrated：2 类或以上感知数据的融合结果。
	SourceType ::= ENUMERATED {
		unknown(0),	-- 0 Unknown
		selfinfo(1),	-- 1 infomation from itself
		v2x(2),	-- 2 v2x
		video(3),	-- 3 video
		microwaveRadar(4),	-- 4 microwave radar
		loop(5),	-- 5 loop
		lidar(6),
		integrated(7),
		...
		}
	
END
