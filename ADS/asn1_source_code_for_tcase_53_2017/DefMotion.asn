/**
 * 定义了车辆速度，航向角，方向盘转角，及其精度相关数据帧和数据元素
 */
DefMotion DEFINITIONS AUTOMATIC TAGS ::= BEGIN


EXPORTS Speed, Heading, SteeringWheelAngle, MotionConfidenceSet, CoarseHeading;
IMPORTS ;
	
	-- 车辆或其他交通参与者的速度大小。
	-- 分辨率为0.02 m/s。数值8191表示无效数值。
	Speed ::= INTEGER (0..8191)

	-- 车辆或交通参与者的航向角。为运动方向与正北方向的顺时针夹角。（细粒度）
	-- 分辨率为0.0125°。
	-- A range of 0 to 359.9875 degrees
	Heading ::= INTEGER (0..28800) 
	
	-- 定义粗粒度的车辆航向角。
	-- Where the LSB is in units of 1.5 degrees
	-- over a range of 0~358.5 degrees
	-- the value 240 shall be used for unavailable
	CoarseHeading ::= INTEGER (0..240)

	
	-- 定义车辆方向盘转角。向右为正，向左为负。
	-- 分辨率为1.5°。数值127为无效数值。
	-- LSB units of 1.5 degrees, a range of -189 to +189 degrees
	-- +001 = +1.5 deg
	-- -126 = -189 deg and beyond
	-- +126 = +189 deg and beyond
	-- +127 to be used for unavailable
	SteeringWheelAngle ::= INTEGER (-126..127)
	
	-- 描述车辆运行状态的精度。
	-- 包括车速精度、航向精度和方向盘转角的精度。组合类型
	MotionConfidenceSet ::= SEQUENCE {
		speedCfd SpeedConfidence OPTIONAL,
		headingCfd HeadingConfidence OPTIONAL,
		steerCfd SteeringWheelAngleConfidence OPTIONAL
	}
	
	-- 数值描述了95%置信水平的航向精度。该精度理论上只考虑了当前航向传感器的误差。但是，当系
	-- 统能够自动检测错误并修正，相应的精度数值也应该提高。
	HeadingConfidence ::= ENUMERATED {
		unavailable (0), -- B'000 Not Equipped or unavailable
		prec10deg (1), -- B'010 10 degrees
		prec05deg (2), -- B'011 5 degrees
		prec01deg (3), -- B'100 1 degrees
		prec0-1deg (4), -- B'101 0.1 degrees
		prec0-05deg (5), -- B'110 0.05 degrees
		prec0-01deg (6), -- B'110 0.01 degrees
		prec0-0125deg (7) -- B'111 0.0125 degrees, aligned with heading LSB
		} -- Encoded as a 3 bit value
	
	-- 数值描述了95%置信水平的速度精度。该精度理论上只考虑了当前速度传感器的误差。但是，当系
	-- 统能够自动检测错误并修正，相应的精度数值也应该提高
	SpeedConfidence ::= ENUMERATED {
		unavailable (0), -- Not Equipped or unavailable
		prec100ms (1), -- 100 meters / sec
		prec10ms (2), -- 10 meters / sec
		prec5ms (3), -- 5 meters / sec
		prec1ms (4), -- 1 meters / sec
		prec0-1ms (5), -- 0.1 meters / sec
		prec0-05ms (6), -- 0.05 meters / sec
		prec0-01ms (7) -- 0.01 meters / sec
		}-- Encoded as a 3 bit value
	
	-- 数值描述了95%置信水平的车辆方向盘转角精度
	SteeringWheelAngleConfidence ::= ENUMERATED {
		unavailable (0), -- B'00 Not Equipped with Wheel angle
		-- or Wheel angle status is unavailable
		prec2deg (1), -- B'01 2 degrees
		prec1deg (2), -- B'10 1 degree
		prec0-02deg (3) -- B'11 0.02 degrees
		}-- Encoded as a 2 bit value
	
	
END
